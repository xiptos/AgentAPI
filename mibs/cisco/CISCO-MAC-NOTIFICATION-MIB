-- MIB file created 02-Dec-2001 21:59:29, by
--   SMICng version 2.2.11-beta(PRO)(Solaris), January 20, 2001. Enterprise key cisco.com

CISCO-MAC-NOTIFICATION-MIB DEFINITIONS ::= BEGIN

-- From file: "CISCO-MAC-NOTIFICATION-MIB.my"
-- Compile options "4 7 F H N W 03 06 0B 0G 0N 0T"

IMPORTS
    TruthValue, TimeStamp
            FROM SNMPv2-TC-v1
    ifIndex
            FROM IF-MIB
    ciscoMgmt
            FROM CISCO-SMI
    Counter, Gauge
            FROM RFC1155-SMI
    OBJECT-TYPE
            FROM RFC-1212
    TRAP-TYPE
            FROM RFC-1215;

ciscoMacNotificationMIB OBJECT IDENTIFIER ::= { ciscoMgmt 215 }
-- MODULE-IDENTITY
--  LastUpdated
--    200110220000Z
--  OrgName
--    Cisco Systems, Inc.
--  ContactInfo
--           Cisco Systems
--            Customer Service
--    
--            Postal: 170 W Tasman Drive
--                    San Jose, CA  95134
--                    USA
--    
--            Tel: +1 800 553-NETS
--    
--            E-mail: cs-wbu@cisco.com
--  Descr
--    This MIB module is for configuration of the MAC notification
--    feature. MAC notification is a mechanism to inform monitoring
--    devices when there are MAC addresses learnt or removed from
--    the forwarding database of the monitored devices.
--  RevDate
--    200110220000Z
--  RevDescr
--    Initial version of this MIB module.

ciscoMacNotificationMIBObjects OBJECT IDENTIFIER ::= { ciscoMacNotificationMIB 1 }
cmnGlobalObjects OBJECT IDENTIFIER ::= { ciscoMacNotificationMIBObjects 1 }
cmnInterfaceObjects OBJECT IDENTIFIER ::= { ciscoMacNotificationMIBObjects 2 }
cmnMIBNotificationPrefix OBJECT IDENTIFIER ::= { ciscoMacNotificationMIB 2 }
cmnMIBNotifications OBJECT IDENTIFIER ::= { cmnMIBNotificationPrefix 0 }
cmnMIBConformance OBJECT IDENTIFIER ::= { ciscoMacNotificationMIB 3 }
cmnMIBCompliances OBJECT IDENTIFIER ::= { cmnMIBConformance 1 }
cmnMIBGroups    OBJECT IDENTIFIER ::= { cmnMIBConformance 2 }

cmnGlobalFeatureEnabled OBJECT-TYPE
    SYNTAX TruthValue
--    Rsyntax INTEGER {
--        true(1),
--        false(2)
--        }
    ACCESS read-write
    STATUS mandatory
    DESCRIPTION
        "Indicates whether the MAC notification feature is currently 
        running in the device.
        
        Setting this object to false(2) disables the MAC notification
        feature globally thus disabling the feature at each interface.
        
        Setting this object to true(1) will start the MAC notification
        feature running in the device. If the feature is already
        running, setting to true(1) has no effect. Once the MAC
        notification is enabled, whether the feature is running at each
        interface is controlled by the cmnIfConfigTable."
    ::= { cmnGlobalObjects 1 }

cmnNotificationInterval OBJECT-TYPE
    SYNTAX Gauge(0..4294967295)
--  Units
--    seconds
    ACCESS read-write
    STATUS mandatory
    DESCRIPTION
        "This object specifies the maximum interval of time between
        cmnMacChangedNotifications being generated by the device.
        If the value of cmnNotificationsEnabled is true(1), the
        device will send out the generated cmnMacChangedNotifications
        and archive the MAC change notification events in the
        cmnHistoryTable. If the value of cmnNotificationEnabled is
        false(2), the device will not send out the generated
        cmnMacChangedNotifications but it will archive these events
        in the cmnHistoryTable.   
        
        If the value of this object is equal to 0, the device will 
        generate cmnMacChangedNotifications and archive the MAC 
        change notification events in the cmnHistoryTable as soon as
        there is MAC address learnt or removed by the device.
        
        If the value of this object is greater than 0, the device will
        wait for a period of time equal to the value of this object
        before generate the cmnMacChangedNotifications and archive
        the MAC change notification events in the cmnHistoryTable."
    DEFVAL { 1 }
    ::= { cmnGlobalObjects 2 }

cmnMacAddressesLearnt OBJECT-TYPE
    SYNTAX Counter
    ACCESS read-only
    STATUS mandatory
    DESCRIPTION
        "Indicates the number of MAC addresses learnt by the
        device."
    ::= { cmnGlobalObjects 3 }

cmnMacAddressesRemoved OBJECT-TYPE
    SYNTAX Counter
    ACCESS read-only
    STATUS mandatory
    DESCRIPTION
        "Indicates the number of MAC addresses removed from the
        forwarding database."
    ::= { cmnGlobalObjects 4 }

cmnNotificationsEnabled OBJECT-TYPE
    SYNTAX TruthValue
--    Rsyntax INTEGER {
--        true(1),
--        false(2)
--        }
    ACCESS read-write
    STATUS mandatory
    DESCRIPTION
        "Indicates whether cmnMacChangedNotification notifications
         will or will not be sent when there are MAC addresses
         learnt or removed from the device's forwarding database. 
         Disabling notifications does not prevent the MAC address
         info from being added to the cmnHistoryTable."
    DEFVAL { false }
    ::= { cmnGlobalObjects 5 }

cmnNotificationsSent OBJECT-TYPE
    SYNTAX Counter
    ACCESS read-only
    STATUS mandatory
    DESCRIPTION
        "Indicates the number of cmnMacChangedNotifications sent out
        by the device."
    ::= { cmnGlobalObjects 6 }

cmnHistTableMaxLength OBJECT-TYPE
    SYNTAX Gauge(0..500)
--  Units
--    entries
    ACCESS read-write
    STATUS mandatory
    DESCRIPTION
        "The upper limit on the number of entries that the
        cmnHistoryTable may contain.  A value of 0 will
        prevent any history from being retained. When this
        table is full, the oldest entry will be deleted and
        a new one will be created."
    DEFVAL { 1 }
    ::= { cmnGlobalObjects 7 }

cmnHistoryTable OBJECT-TYPE
    SYNTAX SEQUENCE OF CmnHistoryEntry
    ACCESS not-accessible
    STATUS mandatory
    DESCRIPTION
        "This table will archive the MAC change notification events 
        generated by this device. The MAC change notification
        events are archived here even if cmnMacChangesNotifications 
        are not actually sent."
    ::= { cmnGlobalObjects 8 }

cmnHistoryEntry OBJECT-TYPE
    SYNTAX CmnHistoryEntry
    ACCESS not-accessible
    STATUS mandatory
    DESCRIPTION
        "A MAC change notification message that was previously
        generated by this device.  Each entry is indexed by a message
        index."
    INDEX { cmnHistIndex }
    ::= { cmnHistoryTable 1 }

CmnHistoryEntry ::= SEQUENCE {
    cmnHistIndex Gauge,
    cmnHistMacChangedMsg OCTET STRING,
    cmnHistTimestamp TimeStamp
    }

cmnHistIndex OBJECT-TYPE
    SYNTAX Gauge(1..4294967295)
    ACCESS not-accessible
    STATUS mandatory
    DESCRIPTION
        "An index that uniquely identifies a MAC change notification
        event previously generated by the device. This index starts at
        1 and increases by one when a MAC change notification is 
        generated.  When it reaches the maximum value, the agent wraps
        the value back to 1."
    ::= { cmnHistoryEntry 1 }

cmnHistMacChangedMsg OBJECT-TYPE
    SYNTAX OCTET STRING(SIZE(1..254))
    ACCESS read-only
    STATUS mandatory
    DESCRIPTION
        "This object contains the information of a MAC change
        notification event. It consists of several tuples packed
        together in the format of '<tuple1><tuple2>...'.
        
        Each tuple consist of 11 octets in the format of
        '<operation><VLAN><MAC><dot1dBasePort>' where 
        
        <operation> is of size 1 octet and supports the following values
          0 - End of MIB object.
          1 - MAC learnt.
          2 - MAC removed.
        
        <VLAN> is vlan number of the VLAN which the MAC address is
        belonged to and has size of 2 octet.
        
        <MAC> is the Layer2 Mac Address and has size of 6 octets.
        
        <dot1dBasePort> is the value of dot1dBasePort for the
        interface from which the MAC address is learnt and has size
        of 2 octets."
    ::= { cmnHistoryEntry 2 }

cmnHistTimestamp OBJECT-TYPE
    SYNTAX TimeStamp
--    Rsyntax TimeTicks
    ACCESS read-only
    STATUS mandatory
    DESCRIPTION
        "The value of sysUpTime when the cmnMacChangedNotification
        containing the information denoted by the cmnHistMacChangedMsg
        object in this entry was generated."
    ::= { cmnHistoryEntry 3 }

cmnIfConfigTable OBJECT-TYPE
    SYNTAX SEQUENCE OF CmnIfConfigEntry
    ACCESS not-accessible
    STATUS mandatory
    DESCRIPTION
        "This table enables or disables the generation of notification
        at each interface when MAC address is learnt or removed."
    ::= { cmnInterfaceObjects 1 }

cmnIfConfigEntry OBJECT-TYPE
    SYNTAX CmnIfConfigEntry
    ACCESS not-accessible
    STATUS mandatory
    DESCRIPTION
        "Each entry contains the configuration for enabling the
        MAC notification at each interface that supports this
        feature."
    INDEX { ifIndex }
    ::= { cmnIfConfigTable 1 }

CmnIfConfigEntry ::= SEQUENCE {
    cmnMacAddrLearntEnable TruthValue,
    cmnMacAddrRemovedEnable TruthValue
    }

cmnMacAddrLearntEnable OBJECT-TYPE
    SYNTAX TruthValue
--    Rsyntax INTEGER {
--        true(1),
--        false(2)
--        }
    ACCESS read-write
    STATUS mandatory
    DESCRIPTION
        "Indicates whether this interface is enabled to send 
        cmnMacChangedNotification when it learns a new MAC address. This
        variable has no effect when the value of cmnGlobalFeatureEnabled
        object is false(2).
        
        Setting this object to true(1) enables the sending of
        cmnMacChangedNotification when this interface learns a 
        new MAC address.
        
        Setting this object to false(2) disables the sending
        of cmnMacChangedNotification when this interface learns
        a new MAC address."
    DEFVAL { false }
    ::= { cmnIfConfigEntry 1 }

cmnMacAddrRemovedEnable OBJECT-TYPE
    SYNTAX TruthValue
--    Rsyntax INTEGER {
--        true(1),
--        false(2)
--        }
    ACCESS read-write
    STATUS mandatory
    DESCRIPTION
        "Indicates whether this interface is enabled to send 
        cmnMacChangedNotification when a MAC address which it learnt
        previously is removed from the forwarding table. This variable
        has no effect when the value of cmnGlobalFeatureEnabled object
        is false(2). 
        
        Setting this object to true(1) enables the sending of
        cmnMacChangedNotification when a MAC address which this
        interface learnt previously is removed from the forwarding
        table.
        
        Setting this object to false(2) disables the sending of
        cmnMacChangedNotification when a MAC address which this
        interface learnt previously is removed from the forwarding
        table."
    DEFVAL { false }
    ::= { cmnIfConfigEntry 2 }

cmnMacChangedNotification TRAP-TYPE
-- Reverse mappable trap
    ENTERPRISE cmnMIBNotificationPrefix
    VARIABLES {
        cmnHistMacChangedMsg, cmnHistTimestamp }
--  Status
--    mandatory
    DESCRIPTION
        "This notification is generated when there is enough MAC
        address information to fully occupy a maximum size SNMP trap
        message. This notification is also generated when there
        is at least one MAC address changed or removed and the amount
        of time elapsed from the previous notification is greater
        than the maximum wait time denoted by 
        cmnNotificationInterval object. 
        
        If there are more MAC addresses information than can fit into
        one cmmHistTrapContent object, then multiple notifications
        will be generated."
    ::= 1

cmnGlobalGroup OBJECT IDENTIFIER ::= { cmnMIBGroups 1 }
-- OBJECT-GROUP
--  Status
--    mandatory
--  Descr
--    A collection of objects providing the global configuration
--    and information for MAC notification.
--  objects
--    cmnGlobalFeatureEnabled, cmnNotificationInterval, 
--    cmnMacAddressesLearnt, cmnMacAddressesRemoved, 
--    cmnNotificationsEnabled, cmnHistTableMaxLength, 
--    cmnHistMacChangedMsg, cmnHistTimestamp, cmnNotificationsSent

cmnInterfaceGroup OBJECT IDENTIFIER ::= { cmnMIBGroups 2 }
-- OBJECT-GROUP
--  Status
--    mandatory
--  Descr
--    A collection of objects providing the configuration information
--    for MAC notification at each interface.
--  objects
--    cmnMacAddrLearntEnable, cmnMacAddrRemovedEnable

cmnNotificationGroup OBJECT IDENTIFIER ::= { cmnMIBGroups 3 }
-- NOTIFICATION-GROUP
--  Status
--    mandatory
--  Descr
--    The notification generated by the CISCO-MAC-NOTIFICATION-MIB.
--  notifications
--    cmnMacChangedNotification

cmnMIBCompliance OBJECT IDENTIFIER ::= { cmnMIBCompliances 1 }
-- MODULE-COMPLIANCE
--  Status
--    mandatory
--  Descr
--    The compliance statement for the CISCO-MAC-NOTIFICATION-MIB.
--  Module
--    >>current<<
--   MandGroup
--    cmnGlobalGroup
--   MandGroup
--    cmnInterfaceGroup
--   MandGroup
--    cmnNotificationGroup


END
